# 17. ReqIF Tutorial Export
Export EA from C:\hoData\Development\GitHub\EnterpriseArchitect_hoReverse\Resources\ReqIfTutorial.eapx

# Specification: Module ExportModule1
- ReqIF.Name: ExportModule1
- ReqIF.Description: Sonderzeichen: §$%&
  My lovely module description with bullet points
  11111
  - Bullet
  - Another bullet
  1. Number 1
  2. Number 2

## {77CB3612-5A6B-4a5c-8389-2D5281401A0F}: Example
Some description for EA Notes
Ordered list:
1. dddd
2. 2eeee
3. fff
Unordered list:
- one line
- another line
- an another line
Some formatting:
Bold
Italic
Understrike
Colours Blue, Red, Green
ffff^Superscript
ffffff_Subscript
Link: https://github.com/Helmut-Ortmann/EnterpriseArchitect_hoReverse
- _typeEnum: Heading
- _comment: My comment
- _state: Accepted

### {E9413C6E-2790-421d-A824-E19B53127D1F}: ExampleFormatting Notes
For smooth integration of tools you should use EA Notes. They supports what is essential for requirements engineering.
By, the way: Searching is much easier.
Some description for EA Notes
Ordered list:
1. dddd
2. 2eeee
3. fff
Unordered list:
- first
- second third
- third
Some formatting:
Bold
Italic
Understrike
Colours Blue, Red, Green
ffff^Superscript
ffffff_Subscript
Link: https://github.com/Helmut-Ortmann/EnterpriseArchitect_hoReverse
- _typeEnum: Information
- _state: Accepted

### {428BC3EC-B999-4dab-936B-046B7F6E4125}: ExampleFormatting LinkedDocument
A warning up front:
Most ReqIF tools stick to basic formatting like:
- Ordered lists
- Unordered list
- Simple text
- simple formatting like bold, italic, understrike, ...
EA supports such basic formatting with it’s notes fields. Usually no need for advanced formatting with EA Linked Documents.
Some formatting:
Ordered list:
1. First
2. Second
3. Third
Unordered list:
- one item
- another item
- and another item
Indentation:
Most modern requirement authoring tools emulate word processors, but offer additional features. This allows authors of requirement specifications who have been using word processors to continue working in a similar manner, but enjoy the benefits of a tool specialized for authoring requirements.
Below picture shows an example for the transition from creating a textual document using a word processor to authoring a specification in a modern requirements authoring tool.
Formatting:
Bold
Italic
Colours:
Red, Green, Blue
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Table
| Header 1 | Header 2 | Header 3 |
| --- | --- | --- |
| Row 1 | Red |  |
| Row 2 | Green |  |
| Row 3 | Blue |  |
Embedded Files:
- _typeEnum: Requirement
- _toDoChecklist: DetailedDesign, Implementation, Verification
- _state: Rejected

## {BAA916CD-2620-40c7-92F6-AEDECCE12FCB}: Requirement1
Some description
1. dddd
2. 2eeee
3. fff
- _typeEnum: Heading
- _state: Accepted

### {D1FBDEEC-80CE-4532-A7E1-E72CBD80E012}: Requirement1.1
Linked Document
Heading 1
Supports:
- Graphics
- Colours
- Embedded Files
-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
Heading 2
Embedded Files:
- _typeEnum: Information
- _state: Accepted

### {1B359A55-E4E5-406d-9802-8AEFC8ADC817}: Requirement1.2
Requirement1.2:
Some description
1. dddd
2. 2eeee
3. fff
- _typeEnum: Requirement
- _toDoChecklist: Implementation
- _state: Accepted

## {94554701-F1A8-42e9-8347-58F9DA2F6222}: Requirement_2
Some description
1. dddd
2. 2eeee
3. fff
- _typeEnum: Heading
- _state: Init

### {3BC27D57-5F55-4aed-B15A-2437739BBC19}: Requirement_2.1
A picture
Concider:
- Req016
- Req017
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Embedded Files:
- _typeEnum: Requirement
- _toDoChecklist: Archutecture, DetailedDesign
- _state: Init

### {77E7B564-688C-4553-B94C-9BE8AE1160A3}: Requirement_2.2
Some description
1. dddd
2. 2eeee
3. fff
- _typeEnum: Heading
- _state: Accepted

#### {F27B51F2-253F-4e2c-BA87-C40613FCBE1A}: Requirement_2.2.1
Some description
1. dddd
2. 2eeee
3. fff
Some more descriptions
- first
- second
- third
- _typeEnum: Information
- _state: Accepted

#### {B914782E-6C3B-45c1-81E2-F0FF36043AE7}: Requirement_2.2.2
Some description
1. dddd
2. 2eeee
3. fff
- _typeEnum: Requirement
- _toDoChecklist: Verification
- _state: ReadyReview
