# IBM Rational DOORS, 07 June 2018

# Specification: module A
- ReqIF.Description: Details of Modul A
- ReqIF.Name: module A

## 1: Headline A

### 2
Col_A Col_B Col_B
A1 A2 A3
A2 B2 B3
tabelle created in Word and copied to Doors

### 3
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a screenshot of icon from Word

### 4
ColA Col B ColB with Blanks
A1 A2 A3
A2 B2 B4

### 5
ColA Col B ColB
A1 ddddddddddddd d A2 dddddddd A3ffffffffffffff
A2 B2 B4

### 6
Excel cut and paste
Header 1 Header 2 Header 3 Header 4
aaa dddd
ccccc vvvv
aaa dddd
ccccc vvvv dddd ccc bbb fffff

### 7
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OLE Object

### 8
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OLE *.csv

### 15: Heading 1.1

#### 22
Hier ein Text mit A^2 (2 oben als Exponent) und B_Keller (Keller als superscript unten)

#### 16

##### 9
- Meine Bullet-Liste
- Meine Bullet-Liste
- Meine Bullet-Liste
- Meine Bullet-Liste
- ^dddddddddddddd
- _Meine Bullet-Liste
- ggggggggggggggggggggg

##### 10
- ddddddddd
- ddddddd
- ffffffffff
- ffffff gggggggg (with tab)

##### 11
ddddddd
fffffff
ggggg
hhhhh
hhhhhh
Einrücken with three blanks ' ' between ''

##### 12
Another Bullet list:

### 14: PDF

#### 17
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
#### 18
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
### 13: Excel

#### 19
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
#### 20
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
#### 21
End

# Specification: module B
- ReqIF.Name: module B

## 1: Header 1

### 2
Requirement 1
- ManuellLink -> 3

### 3
Requirement 2
- ManuellLink -> 22

### 4
Requirement 3
- ManuellLink -> 10

## 5: Header 2

## 6

## 7
